DEFINITIONS EXPLICIT TAGS ::=
BEGIN
I ::= SEQUENCE OF INTEGER
END


INSTANTIATE { "I": [
  "158484376327328453995483472161293205490658676732612761283495965405495438234732",
  "-158484376327328453995483472161293205490658676732612761283495965405495438234732",
  "0",
  "-0",
  "1",
  "-1",
  "127",
  "-127",
  "128",
  "-128",
  "129",
  "-129"
] }


DER:
30 UNIVERSAL 16 (SEQUENCE, SEQUENCE OF) CONSTRUCTED
67 LENGTH 103
  02 UNIVERSAL 2 (INTEGER) PRIMITIVE
  21 LENGTH 33
  01 5E 62 FA 6A 9C A3 4A D1 D6 F6 88 66 25 E0 CF 8B 63 D7 78 4E 28 2D D5 18 12 CC BA A1 E2 0A 54 6C CONTENTS 158484376327328453995483472161293205490658676732612761283495965405495438234732
  02 UNIVERSAL 2 (INTEGER) PRIMITIVE
  21 LENGTH 33
  FE A1 9D 05 95 63 5C B5 2E 29 09 77 99 DA 1F 30 74 9C 28 87 B1 D7 D2 2A E7 ED 33 45 5E 1D F5 AB 94 CONTENTS -158484376327328453995483472161293205490658676732612761283495965405495438234732
  02 UNIVERSAL 2 (INTEGER) PRIMITIVE
  01 LENGTH 1
  00 CONTENTS 0
  02 UNIVERSAL 2 (INTEGER) PRIMITIVE
  01 LENGTH 1
  00 CONTENTS 0
  02 UNIVERSAL 2 (INTEGER) PRIMITIVE
  01 LENGTH 1
  01 CONTENTS 1
  02 UNIVERSAL 2 (INTEGER) PRIMITIVE
  01 LENGTH 1
  FF CONTENTS -1
  02 UNIVERSAL 2 (INTEGER) PRIMITIVE
  01 LENGTH 1
  7F CONTENTS 127
  02 UNIVERSAL 2 (INTEGER) PRIMITIVE
  01 LENGTH 1
  81 CONTENTS -127
  02 UNIVERSAL 2 (INTEGER) PRIMITIVE
  02 LENGTH 2
  00 80 CONTENTS 128
  02 UNIVERSAL 2 (INTEGER) PRIMITIVE
  01 LENGTH 1
  80 CONTENTS -128
  02 UNIVERSAL 2 (INTEGER) PRIMITIVE
  02 LENGTH 2
  00 81 CONTENTS 129
  02 UNIVERSAL 2 (INTEGER) PRIMITIVE
  02 LENGTH 2
  FF 7F CONTENTS -129
