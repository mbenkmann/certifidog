DEFINITIONS EXPLICIT TAGS ::=
BEGIN
B ::= BIT STRING {
  wusel(3),
  dusel(7)
}
S ::= SEQUENCE OF B
END


INSTANTIATE { "S": [
    "",
    "0b0",
    "0b1",
    "wusel dusel",
    "0b1111",
    "0b0001",
    "0b1001 1100",
    "0x12345678"
  ]
}


JSON(no-bit-names):
[
  "",
  "0b0",
  "0b1",
  "0b00010001",
  "0b1111",
  "0b0001",
  "0b10011100",
  "0x12 34 56 78"
]
