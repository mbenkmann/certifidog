DEFINITIONS EXPLICIT TAGS ::=
BEGIN

a  OCTET STRING ::= "Hallo"
b1  BOOLEAN ::= FALSE
b2  BOOLEAN ::= TRUE
d1 INTEGER ::= 1234
d2 INTEGER ::= -99
d3 INTEGER ::= 00009999999999999999999999999999
f  OBJECT IDENTIFIER ::= {1 2 3}
n NULL ::= NULL

END


DEFINITIONS EXPLICIT TAGS ::=
BEGIN

a  OCTET STRING ::= "Hallo"
b1  BOOLEAN ::= FALSE
b2  BOOLEAN ::= TRUE
d1 INTEGER ::= 1234
d2 INTEGER ::= -99
d3 INTEGER ::= 9999999999999999999999999999
f  OBJECT IDENTIFIER ::= { 1 2 3 }
n NULL ::= NULL

END
