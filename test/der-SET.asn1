DEFINITIONS EXPLICIT TAGS ::=
BEGIN
Fruit ::= ENUMERATED {
  apple(0),
  banana(1),
  cherry(2)
}

Set ::= SET {
  b1 [7] BOOLEAN DEFAULT TRUE,
  b2 [2] BOOLEAN DEFAULT FALSE,
  i1 [1] INTEGER DEFAULT -1,
  i2 [6] INTEGER DEFAULT -2,
  f1 [8] Fruit DEFAULT apple,
  f2 [3] Fruit DEFAULT 1,
  u1 [4] UTF8String DEFAULT "Hallo",
  u2 [5] UTF8String DEFAULT "Bye",
  f3 [0] Fruit DEFAULT cherry
}

Set2 ::= SET {
  s1 [1] Set,
  s2 [0] Set,
  s3 [2] Set
}
END


INSTANTIATE { 
  "Set2": {
    "s2":{"b1":true,  "b2":true,  "i1":77, "i2":-2, "f1":2, "f2":2,        "u1":"Hallo", "u2":"byE",  "f3":"apple" }, 
    "s1":{"b1":false, "b2":false, "i1":-1, "i2":-1, "f1":0, "f2":"banana", "u1":"Welt!", "u2":"Bye", "f3":"cherry" },
    "s3":{            "b2":true,  "i1":-77,         "f1":2, "f2":2,                      "u2":"byE",  "f3":"apple"}
  } 
}


DER:
31 UNIVERSAL 17 (SET, SET OF) CONSTRUCTED
5F LENGTH 95
  A0 CONTEXT-SPECIFIC 0 CONSTRUCTED
  22 LENGTH 34
    31 UNIVERSAL 17 (SET, SET OF) CONSTRUCTED
    20 LENGTH 32
      A0 CONTEXT-SPECIFIC 0 CONSTRUCTED
      03 LENGTH 3
        0A UNIVERSAL 10 (ENUMERATED) PRIMITIVE
        01 LENGTH 1
        00 CONTENTS
      A1 CONTEXT-SPECIFIC 1 CONSTRUCTED
      03 LENGTH 3
        02 UNIVERSAL 2 (INTEGER) PRIMITIVE
        01 LENGTH 1
        4D CONTENTS 77
      A2 CONTEXT-SPECIFIC 2 CONSTRUCTED
      03 LENGTH 3
        01 UNIVERSAL 1 (BOOLEAN) PRIMITIVE
        01 LENGTH 1
        FF CONTENTS
      A3 CONTEXT-SPECIFIC 3 CONSTRUCTED
      03 LENGTH 3
        0A UNIVERSAL 10 (ENUMERATED) PRIMITIVE
        01 LENGTH 1
        02 CONTENTS
      A5 CONTEXT-SPECIFIC 5 CONSTRUCTED
      05 LENGTH 5
        0C UNIVERSAL 12 (UTF8String) PRIMITIVE
        03 LENGTH 3
        62 79 45 CONTENTS "byE"
      A8 CONTEXT-SPECIFIC 8 CONSTRUCTED
      03 LENGTH 3
        0A UNIVERSAL 10 (ENUMERATED) PRIMITIVE
        01 LENGTH 1
        02 CONTENTS
  A1 CONTEXT-SPECIFIC 1 CONSTRUCTED
  15 LENGTH 21
    31 UNIVERSAL 17 (SET, SET OF) CONSTRUCTED
    13 LENGTH 19
      A4 CONTEXT-SPECIFIC 4 CONSTRUCTED
      07 LENGTH 7
        0C UNIVERSAL 12 (UTF8String) PRIMITIVE
        05 LENGTH 5
        57 65 6C 74 21 CONTENTS "Welt!"
      A6 CONTEXT-SPECIFIC 6 CONSTRUCTED
      03 LENGTH 3
        02 UNIVERSAL 2 (INTEGER) PRIMITIVE
        01 LENGTH 1
        FF CONTENTS -1
      A7 CONTEXT-SPECIFIC 7 CONSTRUCTED
      03 LENGTH 3
        01 UNIVERSAL 1 (BOOLEAN) PRIMITIVE
        01 LENGTH 1
        00 CONTENTS
  A2 CONTEXT-SPECIFIC 2 CONSTRUCTED
  22 LENGTH 34
    31 UNIVERSAL 17 (SET, SET OF) CONSTRUCTED
    20 LENGTH 32
      A0 CONTEXT-SPECIFIC 0 CONSTRUCTED
      03 LENGTH 3
        0A UNIVERSAL 10 (ENUMERATED) PRIMITIVE
        01 LENGTH 1
        00 CONTENTS
      A1 CONTEXT-SPECIFIC 1 CONSTRUCTED
      03 LENGTH 3
        02 UNIVERSAL 2 (INTEGER) PRIMITIVE
        01 LENGTH 1
        B3 CONTENTS -77
      A2 CONTEXT-SPECIFIC 2 CONSTRUCTED
      03 LENGTH 3
        01 UNIVERSAL 1 (BOOLEAN) PRIMITIVE
        01 LENGTH 1
        FF CONTENTS
      A3 CONTEXT-SPECIFIC 3 CONSTRUCTED
      03 LENGTH 3
        0A UNIVERSAL 10 (ENUMERATED) PRIMITIVE
        01 LENGTH 1
        02 CONTENTS
      A5 CONTEXT-SPECIFIC 5 CONSTRUCTED
      05 LENGTH 5
        0C UNIVERSAL 12 (UTF8String) PRIMITIVE
        03 LENGTH 3
        62 79 45 CONTENTS "byE"
      A8 CONTEXT-SPECIFIC 8 CONSTRUCTED
      03 LENGTH 3
        0A UNIVERSAL 10 (ENUMERATED) PRIMITIVE
        01 LENGTH 1
        02 CONTENTS
