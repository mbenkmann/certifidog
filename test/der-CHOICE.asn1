DEFINITIONS EXPLICIT TAGS ::=
BEGIN
C ::= CHOICE {
  i INTEGER,
  b [7] BOOLEAN,
  n1 NULL,
  n2 [8] NULL,
  s [11] IMPLICIT UTF8String,
  c [12] C
}

S ::= SEQUENCE {
  c1 C,
  c2 C,
  c3 C,
  c4 C,
  c5 C,
  c6 [6] IMPLICIT C,
  c7 [7] IMPLICIT C,
  c8 [8] EXPLICIT C
}

END



INSTANTIATE { "S": {
  "c1":{"i":42},
  "c2":{"b":true},
  "c3":{"n1":null},
  "c4":{"n2":"null"},
  "c5":{"s":"Hallo"},
  "c6":{"i":77},
  "c7":{"c":{"c":{"s":"foo"}}},
  "c8":{"c":{"c":{"s":"foo"}}}
 } 
}


DER:
30 UNIVERSAL 16 (SEQUENCE, SEQUENCE OF) CONSTRUCTED
30 LENGTH 48
  02 UNIVERSAL 2 (INTEGER) PRIMITIVE
  01 LENGTH 1
  2A CONTENTS 42
  A7 CONTEXT-SPECIFIC 7 CONSTRUCTED
  03 LENGTH 3
    01 UNIVERSAL 1 (BOOLEAN) PRIMITIVE
    01 LENGTH 1
    FF CONTENTS
  05 UNIVERSAL 5 (NULL) PRIMITIVE
  00 LENGTH 0
  EMPTY CONTENTS
  A8 CONTEXT-SPECIFIC 8 CONSTRUCTED
  02 LENGTH 2
    05 UNIVERSAL 5 (NULL) PRIMITIVE
    00 LENGTH 0
    EMPTY CONTENTS
  8B CONTEXT-SPECIFIC 11 PRIMITIVE
  05 LENGTH 5
  48 61 6C 6C 6F CONTENTS "Hallo"
  A6 CONTEXT-SPECIFIC 6 CONSTRUCTED
  03 LENGTH 3
    02 UNIVERSAL 2 (INTEGER) PRIMITIVE
    01 LENGTH 1
    4D CONTENTS 77
  A7 CONTEXT-SPECIFIC 7 CONSTRUCTED
  09 LENGTH 9
    AC CONTEXT-SPECIFIC 12 CONSTRUCTED
    07 LENGTH 7
      AC CONTEXT-SPECIFIC 12 CONSTRUCTED
      05 LENGTH 5
        8B CONTEXT-SPECIFIC 11 PRIMITIVE
        03 LENGTH 3
        66 6F 6F CONTENTS "foo"
  A8 CONTEXT-SPECIFIC 8 CONSTRUCTED
  09 LENGTH 9
    AC CONTEXT-SPECIFIC 12 CONSTRUCTED
    07 LENGTH 7
      AC CONTEXT-SPECIFIC 12 CONSTRUCTED
      05 LENGTH 5
        8B CONTEXT-SPECIFIC 11 PRIMITIVE
        03 LENGTH 3
        66 6F 6F CONTENTS "foo"
