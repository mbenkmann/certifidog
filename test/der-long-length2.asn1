DEFINITIONS IMPLICIT TAGS ::=
BEGIN

Str ::= UTF8String

END


INSTANTIATE { 
"Str": "Lorem ipsum dolor sit amet, consectetur adipiscing elit. Aliquam laoreet gravida leo eu varius. Quisque magna velit, efficitur."
}


DER:
0C UNIVERSAL 12 (UTF8String) PRIMITIVE
7F LENGTH 127
4C 6F 72 65 6D 20 69 70 73 75 6D 20 64 6F 6C 6F 72 20 73 69 74 20 61 6D 65 74 2C 20 63 6F 6E 73 65 63 74 65 74 75 72 20 61 64 69 70 69 73 63 69 6E 67 20 65 6C 69 74 2E 20 41 6C 69 71 75 61 6D 20 6C 61 6F 72 65 65 74 20 67 72 61 76 69 64 61 20 6C 65 6F 20 65 75 20 76 61 72 69 75 73 2E 20 51 75 69 73 71 75 65 20 6D 61 67 6E 61 20 76 65 6C 69 74 2C 20 65 66 66 69 63 69 74 75 72 2E CONTENTS
