DEFINITIONS EXPLICIT TAGS ::=
BEGIN
I ::= [7] INTEGER
END


INSTANTIATE { "I": 15 }


DER:
A7 CONTEXT-SPECIFIC 7 CONSTRUCTED
03 LENGTH 3
  02 UNIVERSAL 2 (INTEGER) PRIMITIVE
  01 LENGTH 1
  0F CONTENTS 15
