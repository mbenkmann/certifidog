DEFINITIONS IMPLICIT TAGS ::=
BEGIN

Tree ::= [APPLICATION 22] SEQUENCE {
  left [0] Tree OPTIONAL,
  right Baum OPTIONAL,
  value INTEGER
}

Baum ::= Tree

END


INSTANTIATE { 
"Tree": {
    "value": 0,
    "left": { "value": 1, "right": {"value":3}},
    "right": { "value": 4, "left": {"value":5}}
  }
}


DER:
76 APPLICATION 22 CONSTRUCTED
17 LENGTH 23
  A0 CONTEXT-SPECIFIC 0 CONSTRUCTED
  08 LENGTH 8
    76 APPLICATION 22 CONSTRUCTED
    03 LENGTH 3
      02 UNIVERSAL 2 (INTEGER) PRIMITIVE
      01 LENGTH 1
      03 CONTENTS 3
    02 UNIVERSAL 2 (INTEGER) PRIMITIVE
    01 LENGTH 1
    01 CONTENTS 1
  76 APPLICATION 22 CONSTRUCTED
  08 LENGTH 8
    A0 CONTEXT-SPECIFIC 0 CONSTRUCTED
    03 LENGTH 3
      02 UNIVERSAL 2 (INTEGER) PRIMITIVE
      01 LENGTH 1
      05 CONTENTS 5
    02 UNIVERSAL 2 (INTEGER) PRIMITIVE
    01 LENGTH 1
    04 CONTENTS 4
  02 UNIVERSAL 2 (INTEGER) PRIMITIVE
  01 LENGTH 1
  00 CONTENTS 0
