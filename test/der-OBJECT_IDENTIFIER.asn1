DEFINITIONS IMPLICIT TAGS ::=
BEGIN

S ::= SEQUENCE OF OBJECT IDENTIFIER

END


INSTANTIATE {
  "S": ["1 2", "1.2.128", "1 2 840 113549 1", "1.3.6.1.4.1.45753"]
}


DER:
30 UNIVERSAL 16 (SEQUENCE, SEQUENCE OF) CONSTRUCTED
1B LENGTH 27
  06 UNIVERSAL 6 (OBJECT IDENTIFIER) PRIMITIVE
  01 LENGTH 1
  2A CONTENTS 1.2
  06 UNIVERSAL 6 (OBJECT IDENTIFIER) PRIMITIVE
  03 LENGTH 3
  2A 81 00 CONTENTS 1.2.128
  06 UNIVERSAL 6 (OBJECT IDENTIFIER) PRIMITIVE
  07 LENGTH 7
  2A 86 48 86 F7 0D 01 CONTENTS 1.2.840.113549.1
  06 UNIVERSAL 6 (OBJECT IDENTIFIER) PRIMITIVE
  08 LENGTH 8
  2B 06 01 04 01 82 E5 39 CONTENTS 1.3.6.1.4.1.45753
