DEFINITIONS IMPLICIT TAGS ::=
BEGIN

S ::= SET OF INTEGER

END


INSTANTIATE { "S":[-3,-256,-2,-1,255,-256,2,3,255] }


DER:
31 UNIVERSAL 17 (SET, SET OF) CONSTRUCTED
1F LENGTH 31
  02 UNIVERSAL 2 (INTEGER) PRIMITIVE
  01 LENGTH 1
  02 CONTENTS 2
  02 UNIVERSAL 2 (INTEGER) PRIMITIVE
  01 LENGTH 1
  03 CONTENTS 3
  02 UNIVERSAL 2 (INTEGER) PRIMITIVE
  01 LENGTH 1
  FD CONTENTS -3
  02 UNIVERSAL 2 (INTEGER) PRIMITIVE
  01 LENGTH 1
  FE CONTENTS -2
  02 UNIVERSAL 2 (INTEGER) PRIMITIVE
  01 LENGTH 1
  FF CONTENTS -1
  02 UNIVERSAL 2 (INTEGER) PRIMITIVE
  02 LENGTH 2
  00 FF CONTENTS 255
  02 UNIVERSAL 2 (INTEGER) PRIMITIVE
  02 LENGTH 2
  00 FF CONTENTS 255
  02 UNIVERSAL 2 (INTEGER) PRIMITIVE
  02 LENGTH 2
  FF 00 CONTENTS -256
  02 UNIVERSAL 2 (INTEGER) PRIMITIVE
  02 LENGTH 2
  FF 00 CONTENTS -256
