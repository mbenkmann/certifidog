DEFINITIONS EXPLICIT TAGS ::=
BEGIN
Foo ::= SEQUENCE {
  opt INTEGER OPTIONAL,
  def INTEGER DEFAULT -99
}
END

DEFINITIONS EXPLICIT TAGS ::=
BEGIN
Foo ::= SEQUENCE {
  opt INTEGER OPTIONAL,
  def INTEGER DEFAULT -99
}
END
