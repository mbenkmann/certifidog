DEFINITIONS EXPLICIT TAGS ::=
BEGIN
H ::= [30] IMPLICIT INTEGER
I ::= [31] IMPLICIT INTEGER
K ::= [32] IMPLICIT INTEGER
L ::= [33] IMPLICIT H
M ::= H
N ::= L
O ::= M
S ::= [40] IMPLICIT SEQUENCE {
  h H,
  i I,
  k K,
  l L,
  m M,
  n N,
  o O
}
END


INSTANTIATE { "S":{"h": 763, "i": 15, "k": 879298, "l": 12, "m": -999, "n": 64537, "o": -32768} }


DER:
BF 28 CONTEXT-SPECIFIC 40 CONSTRUCTED
20 LENGTH 32
  9E CONTEXT-SPECIFIC 30 PRIMITIVE
  02 LENGTH 2
  02 FB CONTENTS
  9F 1F CONTEXT-SPECIFIC 31 PRIMITIVE
  01 LENGTH 1
  0F CONTENTS
  9F 20 CONTEXT-SPECIFIC 32 PRIMITIVE
  03 LENGTH 3
  0D 6A C2 CONTENTS
  9F 21 CONTEXT-SPECIFIC 33 PRIMITIVE
  01 LENGTH 1
  0C CONTENTS "\f"
  9E CONTEXT-SPECIFIC 30 PRIMITIVE
  02 LENGTH 2
  FC 19 CONTENTS
  9F 21 CONTEXT-SPECIFIC 33 PRIMITIVE
  03 LENGTH 3
  00 FC 19 CONTENTS
  9E CONTEXT-SPECIFIC 30 PRIMITIVE
  02 LENGTH 2
  CONTENTS ARE VALID DER => DECODING
    80 CONTEXT-SPECIFIC 0 PRIMITIVE
    00 LENGTH 0
    EMPTY CONTENTS
