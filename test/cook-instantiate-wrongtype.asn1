DEFINITIONS EXPLICIT TAGS ::=
BEGIN
S ::= SEQUENCE {
    i INTEGER
  }
Coord ::= SEQUENCE {
  x INTEGER,
  y INTEGER
}
END


INSTANTIATE { 
  "S": {
    "a": {
      "x": 10,
      "y": 20
    },
    "i": "$a Coord"
  } 
}

/i: Attempt to instantiate type INTEGER from Instance of type SEQUENCE
