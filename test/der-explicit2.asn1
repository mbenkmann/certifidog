DEFINITIONS EXPLICIT TAGS ::=
BEGIN
I ::= [7] SEQUENCE OF BOOLEAN
END


INSTANTIATE { "I": [true, false, false] }


DER:
A7 CONTEXT-SPECIFIC 7 CONSTRUCTED
0B LENGTH 11
  30 UNIVERSAL 16 (SEQUENCE, SEQUENCE OF) CONSTRUCTED
  09 LENGTH 9
    01 UNIVERSAL 1 (BOOLEAN) PRIMITIVE
    01 LENGTH 1
    FF CONTENTS
    01 UNIVERSAL 1 (BOOLEAN) PRIMITIVE
    01 LENGTH 1
    00 CONTENTS
    01 UNIVERSAL 1 (BOOLEAN) PRIMITIVE
    01 LENGTH 1
    00 CONTENTS
