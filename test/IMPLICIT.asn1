DEFINITIONS IMPLICIT TAGS ::=
BEGIN
A ::= [10] EXPLICIT OCTET STRING
B ::= [UNIVERSAL 20] EXPLICIT INTEGER
C ::= [APPLICATION 30] EXPLICIT BOOLEAN
D ::= [PRIVATE 40] EXPLICIT OBJECT IDENTIFIER
E ::= [11] OCTET STRING
F ::= [UNIVERSAL 22] INTEGER
G ::= [APPLICATION 33] BOOLEAN
H ::= [PRIVATE 44] OBJECT IDENTIFIER
I ::= [12] IMPLICIT OCTET STRING
J ::= [UNIVERSAL 23] IMPLICIT INTEGER
K ::= [APPLICATION 34] IMPLICIT BOOLEAN
L ::= [PRIVATE 45] IMPLICIT OBJECT IDENTIFIER
END

DEFINITIONS IMPLICIT TAGS ::=
BEGIN
A ::= [10] EXPLICIT OCTET STRING
B ::= [UNIVERSAL 20] EXPLICIT INTEGER
C ::= [APPLICATION 30] EXPLICIT BOOLEAN
D ::= [PRIVATE 40] EXPLICIT OBJECT IDENTIFIER
E ::= [11] IMPLICIT OCTET STRING
F ::= [UNIVERSAL 22] IMPLICIT INTEGER
G ::= [APPLICATION 33] IMPLICIT BOOLEAN
H ::= [PRIVATE 44] IMPLICIT OBJECT IDENTIFIER
I ::= [12] IMPLICIT OCTET STRING
J ::= [UNIVERSAL 23] IMPLICIT INTEGER
K ::= [APPLICATION 34] IMPLICIT BOOLEAN
L ::= [PRIVATE 45] IMPLICIT OBJECT IDENTIFIER
END
