DEFINITIONS IMPLICIT TAGS ::=
BEGIN

S ::= SEQUENCE OF INTEGER

END


INSTANTIATE { "S":[-4,-3,-2,-1,0,1,2,3,4] }


DER:
30 UNIVERSAL 16 (SEQUENCE, SEQUENCE OF) CONSTRUCTED
1B LENGTH 27
  02 UNIVERSAL 2 (INTEGER) PRIMITIVE
  01 LENGTH 1
  FC CONTENTS -4
  02 UNIVERSAL 2 (INTEGER) PRIMITIVE
  01 LENGTH 1
  FD CONTENTS -3
  02 UNIVERSAL 2 (INTEGER) PRIMITIVE
  01 LENGTH 1
  FE CONTENTS -2
  02 UNIVERSAL 2 (INTEGER) PRIMITIVE
  01 LENGTH 1
  FF CONTENTS -1
  02 UNIVERSAL 2 (INTEGER) PRIMITIVE
  01 LENGTH 1
  00 CONTENTS 0
  02 UNIVERSAL 2 (INTEGER) PRIMITIVE
  01 LENGTH 1
  01 CONTENTS 1
  02 UNIVERSAL 2 (INTEGER) PRIMITIVE
  01 LENGTH 1
  02 CONTENTS 2
  02 UNIVERSAL 2 (INTEGER) PRIMITIVE
  01 LENGTH 1
  03 CONTENTS 3
  02 UNIVERSAL 2 (INTEGER) PRIMITIVE
  01 LENGTH 1
  04 CONTENTS 4
