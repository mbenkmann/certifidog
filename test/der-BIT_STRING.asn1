DEFINITIONS IMPLICIT TAGS ::=
BEGIN

S ::= SEQUENCE OF BIT STRING

END


INSTANTIATE { 
"S": ["","0b0","0b1","0b10","0b01","0b000000001","0b100000000","0x dea fedde affe"]
}


DER:
30 UNIVERSAL 16 (SEQUENCE, SEQUENCE OF) CONSTRUCTED
26 LENGTH 38
  03 UNIVERSAL 3 (BIT STRING) PRIMITIVE
  01 LENGTH 1
  00 CONTENTS
  03 UNIVERSAL 3 (BIT STRING) PRIMITIVE
  02 LENGTH 2
  07 00 CONTENTS
  03 UNIVERSAL 3 (BIT STRING) PRIMITIVE
  02 LENGTH 2
  07 80 CONTENTS
  03 UNIVERSAL 3 (BIT STRING) PRIMITIVE
  02 LENGTH 2
  06 80 CONTENTS
  03 UNIVERSAL 3 (BIT STRING) PRIMITIVE
  02 LENGTH 2
  06 40 CONTENTS
  03 UNIVERSAL 3 (BIT STRING) PRIMITIVE
  03 LENGTH 3
  07 00 80 CONTENTS
  03 UNIVERSAL 3 (BIT STRING) PRIMITIVE
  03 LENGTH 3
  07 80 00 CONTENTS
  03 UNIVERSAL 3 (BIT STRING) PRIMITIVE
  07 LENGTH 7
  00 DE AF ED DE AF FE CONTENTS
