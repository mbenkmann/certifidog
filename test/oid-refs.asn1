DEFINITIONS EXPLICIT TAGS ::=
BEGIN

arc4 OBJECT IDENTIFIER ::= { arc3 6 }
arc1 OBJECT IDENTIFIER ::= { 000 001 }
arc12 OBJECT IDENTIFIER ::= { arc1 2 }
arc12alias OBJECT IDENTIFIER ::= { arc12 }
arc12alias2 OBJECT IDENTIFIER ::= arc12
arc3 OBJECT IDENTIFIER ::= { arc12alias 3 4 005 }

END

DEFINITIONS EXPLICIT TAGS ::=
BEGIN

arc4 OBJECT IDENTIFIER ::= { 0 1 2 3 4 5 6 }
arc1 OBJECT IDENTIFIER ::= { 0 1 }
arc12 OBJECT IDENTIFIER ::= { 0 1 2 }
arc12alias OBJECT IDENTIFIER ::= { 0 1 2 }
arc12alias2 OBJECT IDENTIFIER ::= { 0 1 2 }
arc3 OBJECT IDENTIFIER ::= { 0 1 2 3 4 5 }

END
