DEFINITIONS EXPLICIT TAGS ::=
BEGIN
I ::= ENUMERATED { apple(0) }
END


INSTANTIATE { "I": "9938475476584983838376546218191912847347431" }


Attempt to instantiate ENUMERATED with number not from allowed set: 9938475476584983838376546218191912847347431
