DEFINITIONS EXPLICIT TAGS ::=
BEGIN
I1 ::= [1] INTEGER
I2 ::= [2] I1
I3 ::= [3] I2
I4 ::= [4] I3
END


INSTANTIATE { "I4": 15 }


DER:
A4 CONTEXT-SPECIFIC 4 CONSTRUCTED
09 LENGTH 9
  A3 CONTEXT-SPECIFIC 3 CONSTRUCTED
  07 LENGTH 7
    A2 CONTEXT-SPECIFIC 2 CONSTRUCTED
    05 LENGTH 5
      A1 CONTEXT-SPECIFIC 1 CONSTRUCTED
      03 LENGTH 3
        02 UNIVERSAL 2 (INTEGER) PRIMITIVE
        01 LENGTH 1
        0F CONTENTS 15
