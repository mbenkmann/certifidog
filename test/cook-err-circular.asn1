DEFINITIONS EXPLICIT TAGS ::=
BEGIN
S ::= SEQUENCE {
  a UTF8String,
  b UTF8String,
  c UTF8String,
  d UTF8String,
  e UTF8String,
  q SEQUENCE OF BOOLEAN,
  x SEQUENCE {
    a UTF8String,
    b UTF8String,
    c UTF8String,
    d UTF8String,
    bq SEQUENCE OF BOOLEAN,
    q SEQUENCE OF BOOLEAN,
    x SEQUENCE {
      a UTF8String,
      b UTF8String,
      c UTF8String,
      bq SEQUENCE OF BOOLEAN,
      ab SEQUENCE OF BOOLEAN
    }
  }
}
END


INSTANTIATE { 
  "S": {
    "a": "11",
    "b": "12",
    "c": "13",
    "d": "14",
    "e": "15",
    "q": ["$ a '11' equals", "$b '12' equals", "$c '13' equals", "$d '14' equals", "$e '15' equals"],
    "x": {
      "a": "21",
      "b": "22",
      "bq": "$a '21' equals c '23' equals",
      "c": "$d",
      "d": "$bq",
      "q": ["$ a '21' equals", "$b '22' equals", "$c '23' equals", "$d '24' equals", "$e '15' equals"],
      "x": {
        "a": "31",
        "ab": ["$ a '31' equals", "$b '32' equals", "$c '33' equals", "$d '24' equals", "$e '15' equals"],
        "b": "32",
        "bq": ["$ a '31' equals", "$b '32' equals", "$c '33' equals", "$d '24' equals", "$e '15' equals"],
        "c": "33"
      }
    }
  } 
}

/x/d: Circular dependendy on field "bq"
