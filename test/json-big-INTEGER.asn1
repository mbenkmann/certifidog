DEFINITIONS EXPLICIT TAGS ::=
BEGIN
I ::= ANY
END


INSTANTIATE { "I": "$  00015999993874674653267282843854857575636363645874984  INTEGER" }


JSON():
"$15999993874674653267282843854857575636363645874984 INTEGER"
