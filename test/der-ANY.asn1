DEFINITIONS EXPLICIT TAGS ::=
BEGIN
S ::= SEQUENCE OF ANY
END


INSTANTIATE { "S": [true, false, true, 1, 2, 3, "foobar", ["a","foo"], null] }


DER:
30 UNIVERSAL 16 (SEQUENCE, SEQUENCE OF) CONSTRUCTED
26 LENGTH 38
  01 UNIVERSAL 1 (BOOLEAN) PRIMITIVE
  01 LENGTH 1
  FF CONTENTS
  01 UNIVERSAL 1 (BOOLEAN) PRIMITIVE
  01 LENGTH 1
  00 CONTENTS
  01 UNIVERSAL 1 (BOOLEAN) PRIMITIVE
  01 LENGTH 1
  FF CONTENTS
  02 UNIVERSAL 2 (INTEGER) PRIMITIVE
  01 LENGTH 1
  01 CONTENTS 1
  02 UNIVERSAL 2 (INTEGER) PRIMITIVE
  01 LENGTH 1
  02 CONTENTS 2
  02 UNIVERSAL 2 (INTEGER) PRIMITIVE
  01 LENGTH 1
  03 CONTENTS 3
  0C UNIVERSAL 12 (UTF8String) PRIMITIVE
  06 LENGTH 6
  66 6F 6F 62 61 72 CONTENTS "foobar"
  30 UNIVERSAL 16 (SEQUENCE, SEQUENCE OF) CONSTRUCTED
  08 LENGTH 8
    0C UNIVERSAL 12 (UTF8String) PRIMITIVE
    01 LENGTH 1
    61 CONTENTS "a"
    0C UNIVERSAL 12 (UTF8String) PRIMITIVE
    03 LENGTH 3
    66 6F 6F CONTENTS "foo"
  05 UNIVERSAL 5 (NULL) PRIMITIVE
  00 LENGTH 0
  EMPTY CONTENTS
