DEFINITIONS EXPLICIT TAGS ::=
BEGIN

foo OBJECT IDENTIFIER ::= { bar fuss 1 2 3 }
bar OBJECT IDENTIFIER ::= { 10 20 }

END

Line 4 column 1: Only the first component of an OBJECT IDENTIFIER definition may be a reference to another value
