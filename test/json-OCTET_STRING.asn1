DEFINITIONS EXPLICIT TAGS ::=
BEGIN
S ::= SEQUENCE OF OCTET STRING
END


INSTANTIATE { "S": [
    "$'0x00' decode(hex)",
    "$'0x8080' decode(hex)",
    "$'0x0a0d' decode(hex)",
    "\\Drü Chünüsün müt nüm Küntrübüss\u000a",
    "echo",
    "$1.2.3.4",
    "$1.2.3.4.5"
  ]
}


JSON():
[
  "\u0000",
  "$'0x80 80' decode(hex)",
  "\n\r",
  "\\Drü Chünüsün müt nüm Küntrübüss\n",
  "echo",
  "$1.2.3.4",
  "\u0001\u0002\u0003\u0004\u0005"
]
