DEFINITIONS EXPLICIT TAGS ::=
BEGIN
Fruit ::= INTEGER {
  apple(0),
  banana(1),
  cherry(2)
}
S ::= SEQUENCE {
  a Fruit,
  b Fruit,
  c Fruit
}
END


INSTANTIATE { "S": { "a":0, "b":"banana", "c":"934567828238937436462728498575216777777436436437218181746346344364361"} }


SEQUENCE { a: apple, b: banana, c: 934567828238937436462728498575216777777436436437218181746346344364361 }
