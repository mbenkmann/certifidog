DEFINITIONS EXPLICIT TAGS ::=
BEGIN
S ::= SEQUENCE {
    point1 ANY,
    point2 [22] ANY
  }

Coord ::= [11] IMPLICIT SEQUENCE {
  x INTEGER,
  y INTEGER
}
END


INSTANTIATE { 
  "S": {
    "a": {
      "x": 10,
      "y": 20
    },
    "point1": "$a Coord",
    "point2": "$a Coord"
  } 
}

DER:
30 UNIVERSAL 16 (SEQUENCE, SEQUENCE OF) CONSTRUCTED
12 LENGTH 18
  AB CONTEXT-SPECIFIC 11 CONSTRUCTED
  06 LENGTH 6
    02 UNIVERSAL 2 (INTEGER) PRIMITIVE
    01 LENGTH 1
    0A CONTENTS 10
    02 UNIVERSAL 2 (INTEGER) PRIMITIVE
    01 LENGTH 1
    14 CONTENTS 20
  B6 CONTEXT-SPECIFIC 22 CONSTRUCTED
  08 LENGTH 8
    AB CONTEXT-SPECIFIC 11 CONSTRUCTED
    06 LENGTH 6
      02 UNIVERSAL 2 (INTEGER) PRIMITIVE
      01 LENGTH 1
      0A CONTENTS 10
      02 UNIVERSAL 2 (INTEGER) PRIMITIVE
      01 LENGTH 1
      14 CONTENTS 20
